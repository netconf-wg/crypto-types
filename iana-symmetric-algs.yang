module iana-symmetric-algs {
  yang-version 1.1;
  namespace "urn:ietf:params:xml:ns:yang:iana-symmetric-algs";
  prefix isa;

  organization
    "IETF NETCONF (Network Configuration) Working Group";

  contact
    "WG Web:   <http://datatracker.ietf.org/wg/netconf/>
     WG List:  <mailto:netconf@ietf.org>
     Author:   Kent Watsen <mailto:kent+ietf@watsen.net>
     Author:   Wang Haiguang <wang.haiguang.shieldlab@huawei.com>";

  description
    "This module defines a typedef for symmetric algorithms, and
     a container for a list of symmetric algorithms supported by
     the server.

     Copyright (c) 2019 IETF Trust and the persons identified
     as authors of the code. All rights reserved.
     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision YYYY-MM-DD {
    description
      "Initial version";
    reference
      "RFC XXXX: Common YANG Data Types for Cryptography";
  }

  // Typedefs

  typedef symmetric-algorithm-type {
    type enumeration {
      enum aes-128-cbc {
        value 1;
        description
          "Encrypt message with AES algorithm in CBC mode with
           a key length of 128 bits.";
        reference
          "RFC 3565: Use of the Advanced Encryption Standard (AES)
           Encryption Algorithm in Cryptographic Message Syntax
           (CMS)";
      }
      enum aes-192-cbc {
        value 2;
        description
          "Encrypt message with AES algorithm in CBC mode with
           a key length of 192 bits";
        reference
          "RFC 3565: Use of the Advanced Encryption Standard (AES)
           Encryption Algorithm in Cryptographic Message Syntax
           (CMS)";
      }
      enum aes-256-cbc {
        value 3;
        description
          "Encrypt message with AES algorithm in CBC mode with
           a key length of 256 bits";
        reference
          "RFC 3565: Use of the Advanced Encryption Standard (AES)
           Encryption Algorithm in Cryptographic Message Syntax
           (CMS)";
      }
      enum aes-128-ctr {
        value 4;
        description
          "Encrypt message with AES algorithm in CTR mode with
           a key length of 128 bits";
        reference
          "RFC 3686:
             Using Advanced Encryption Standard (AES) Counter
             Mode with IPsec Encapsulating Security Payload
             (ESP)";
      }
      enum aes-192-ctr {
        value 5;
        description
          "Encrypt message with AES algorithm in CTR mode with
           a key length of 192 bits";
        reference
          "RFC 3686:
             Using Advanced Encryption Standard (AES) Counter
             Mode with IPsec Encapsulating Security Payload
             (ESP)";
      }
      enum aes-256-ctr {
        value 6;
        description
          "Encrypt message with AES algorithm in CTR mode with
           a key length of 256 bits";
        reference
          "RFC 3686:
             Using Advanced Encryption Standard (AES) Counter
             Mode with IPsec Encapsulating Security Payload
             (ESP)";
      }
      enum des3-cbc-sha1-kd {
        value 7;
        description
          "Encrypt message with 3DES algorithm in CBC mode
           with sha1 function for key derivation";
        reference
          "RFC 3961:
             Encryption and Checksum Specifications for
             Kerberos 5";
      }
      enum rc4-hmac {
        value 8;
        description
          "Encrypt message with rc4 algorithm";
        reference
          "RFC 4757:
             The RC4-HMAC Kerberos Encryption Types Used by
             Microsoft Windows";
      }
      enum rc4-hmac-exp {
        value 9;
        description
          "Encrypt message with rc4 algorithm that is exportable";
        reference
          "RFC 4757:
             The RC4-HMAC Kerberos Encryption Types Used by
             Microsoft Windows";
      }
    }
    description
      "A typedef enumerating various symmetric key algorithms.";
  }

  // Protocol-accessible Nodes

  container supported-symmetric-algorithms {
    config false;
    description
      "A container for a list of supported symmetric algorithms.
       How algorithms come to be supported is outside the scope
       of this module.";
    list supported-symmetric-algorithm {
      key algorithm;
      description
        "A lists of symmetric algorithms supported by the server.";
      leaf algorithm {
        type symmetric-algorithm-type;
        description
          "An symmetric algorithms supported by the server.";
      }
    }
  }

}
