module ex-crypto-types-usage {
  yang-version 1.1;
  namespace "https://example.com/ns/example-crypto-types-usage";
  prefix ectu;

  import ietf-crypto-types {
    prefix ct;
    reference
      "RFC AAAA: YANG Data Types and Groupings for Cryptography";
  }

  organization
    "Example Corporation";
  contact
    "YANG Designer <mailto:yang.designer@example.com>";

  description
    "This example module illustrates the 'symmetric-key-grouping'
     and 'asymmetric-key-grouping' groupings defined in the
    'ietf-crypto-types' module defined in RFC AAAA.";

  revision YYYY-MM-DD {
    description
      "Initial version";
    reference
      "RFC AAAA: Common YANG Data Types for Cryptography";
  }

  container symmetric-keys {
    description
      "A container of symmetric keys.";
    list symmetric-key {
      key "name";
      description
        "A symmetric key";
      leaf name {
        type string;
        description
          "An arbitrary name for this key.";
      }
      uses ct:symmetric-key-grouping {
        augment "key-type/encrypted-symmetric-key/"
              + "encrypted-symmetric-key/encrypted-by" {
          description
            "Augments in a choice statement enabling the
             encrypting key to be any other symmetric or
             asymmetric key.";
          uses encrypted-by-grouping;
        }
      }
    }
  }
  container asymmetric-keys {
    description
      "A container of asymmetric keys.";
    list asymmetric-key {
      key "name";
      leaf name {
        type string;
        description
          "An arbitrary name for this key.";
      }
      uses ct:asymmetric-key-pair-with-certs-grouping {
        augment "private-key-type/encrypted-private-key/"
              + "encrypted-private-key/encrypted-by" {
          description
            "Augments in a choice statement enabling the
             encrypting key to be any other symmetric or
             asymmetric key.";
          uses encrypted-by-grouping;
        }
      }
      description
        "An asymmetric key pair with associated certificates.";
    }
  }
  container passwords {
    description
      "A container of passwords.";
    list password {
      key "name";
      leaf name {
        type string;
        description
          "An arbitrary name for this password.";
      }
      uses ct:password-grouping {
        augment "password-type/encrypted-password/"
              + "encrypted-password/encrypted-by" {
          description
            "Augments in a choice statement enabling the
             encrypting key to be any symmetric or
             asymmetric key.";
          uses encrypted-by-grouping;
        }
      }
      description
        "A password.";
    }
  }

  grouping encrypted-by-grouping {
    description
      "A grouping that defines a choice enabling references
       to other keys.";
    choice encrypted-by {
      mandatory true;
      description
        "A choice amongst other symmetric or asymmetric keys.";
      case symmetric-key-ref {
        leaf symmetric-key-ref {
          type leafref {
            path "/ectu:symmetric-keys/ectu:symmetric-key/"
               + "ectu:name";
          }
          description
            "Identifies the symmetric key that encrypts this key.";
        }
      }
      case asymmetric-key-ref {
        leaf asymmetric-key-ref {
          type leafref {
            path "/ectu:asymmetric-keys/ectu:asymmetric-key/"
               + "ectu:name";
          }
          description
            "Identifies the asymmetric key that encrypts this key.";
        }
      }
    }
  }
}
